module onf-core-model-conditional-packages {
    namespace "urn:onf:params:xml:ns:yang:onf-core-model-conditional-packages";
    prefix onf-core-model-conditional-packages;
    import core-model {
        prefix core-model;
    }
    import microwave-model {
        prefix microwave-model;
    }
    organization "ONF (Open Networking Foundation) Open Transport Working Group - Wireless Transport Project";
    contact "WG Web: <https://www.opennetworking.org/technical-communities/areas/specification/1931-optical-transport>
             WG List:  <mailto:wireless-transport@login.opennetworking.org>
             WG Chair: Lyndon Ong
                       <mailto:lyong@ciena.com>
             WG Chair: Giorgio Cazzaniga
                       <mailto:giorgio.cazzaniga@sm-optics.com>
             Editors:  Thorsten Heinze
                       <mailto:thorsten.heinze@telefonica.com>
                       Martin Skorupski
                       <mailto:martin.skorupski@highstreet-technologies.com>";
    description "This model adds conditional packages to the ONF CoreModel in order to support fault management for object classes NetworkElement, Equipment and Holder.";
    revision 2017-03-20 {
        description "Initial version";
        reference "ONF TR 532: A YANG Data Model for Wireless Networks.";
    }
    /***********************
    * package type-definitions
    **********************/ 
        grouping current-problem-type-g {
            leaf problem-name {
                type string;
                default "not-specified";
                config false;
                description "Name of the alarm according capability::supportedAlarms.";
            }
            uses microwave-model:mw-current-problem-g;
            description "none";
        }
        grouping problem-severity-type-g {
            leaf problem-type-name {
                type string;
                default "Problem kind name not defined.";
                description "Name of the alarm according to AirInterface::AirInterfaceCapability::supportedAlarms";
            }
            leaf problem-type-severity {
                type microwave-model:severity-type;
                description "Severity of this type of alarm.";
            }
            description "none";
        }

    /***********************
    * package object-classes
    **********************/ 
        /***********************
        * package network-element
        **********************/ 
            container network-element-pac {
                leaf network-element {
                    type leafref {
                        path '/core-model:network-element/core-model:uuid';
                    }
                    description "none";
                }
                container network-element-capability {
                    uses onf-core-model-conditional-packages:network-element-capability-g;
                    description "none";
                }
                container network-element-configuration {
                    uses onf-core-model-conditional-packages:network-element-configuration-g;
                    description "none";
                }
                container network-element-status {
                    uses onf-core-model-conditional-packages:network-element-status-g;
                    description "none";
                }
                container network-element-current-problems {
                    uses onf-core-model-conditional-packages:network-element-current-problems-g;
                    description "none";
                }
                description "none";
            }
            grouping network-element-capability-g {
                leaf supported-alarms {
                    type string;
                    config false;
                    description "none";
                }
                description "none";
            }
            grouping network-element-configuration-g {
                list problem-type-severity-list {
                    key 'problem-type-name';
                    uses onf-core-model-conditional-packages:problem-severity-type-g;
                    description "Severity of the problem to be configured.";
                }
                description "none";
            }
            grouping network-element-status-g {
                description "none";
            }
            grouping network-element-current-problems-g {
                list current-problem-list {
                    key 'sequence-number';
                    config false;
                    uses onf-core-model-conditional-packages:current-problem-type-g;
                    description "none";
                }
                description "none";
            }

        /***********************
        * package equipment
        **********************/ 
            list equipment-pac {
                key 'equipment';
                leaf equipment {
                    type leafref {
                        path '/core-model:equipment/core-model:uuid';
                    }
                    description "none";
                }
                container equipment-capability {
                    uses onf-core-model-conditional-packages:equipment-capability-g;
                    description "none";
                }
                container equipment-configuration {
                    uses onf-core-model-conditional-packages:equipment-configuration-g;
                    description "none";
                }
                container equipment-status {
                    uses onf-core-model-conditional-packages:equipment-status-g;
                    description "none";
                }
                container equipment-current-problems {
                    uses onf-core-model-conditional-packages:equipment-current-problems-g;
                    description "none";
                }
                description "none";
            }
            grouping equipment-capability-g {
                leaf supported-alarms {
                    type string;
                    config false;
                    description "Available alarms to be listed. Names are to be separated by commas.";
                }
                description "none";
            }
            grouping equipment-configuration-g {
                list problem-type-severity-list {
                    key 'problem-type-name';
                    uses onf-core-model-conditional-packages:problem-severity-type-g;
                    description "Severity of the problem to be configured.";
                }
                description "none";
            }
            grouping equipment-status-g {
                description "none";
            }
            grouping equipment-current-problems-g {
                list current-problem-list {
                    key 'sequence-number';
                    config false;
                    uses onf-core-model-conditional-packages:current-problem-type-g;
                    description "none";
                }
                description "none";
            }

        /***********************
        * package holder
        **********************/ 
            list holder-pac {
                key 'holder';
                leaf holder {
                    type leafref {
                        path '/core-model:equipment/core-model:contained-holder/core-model:uuid';
                    }
                    description "none";
                }
                container holder-capability {
                    uses onf-core-model-conditional-packages:holder-capability-g;
                    description "none";
                }
                container holder-configuration {
                    uses onf-core-model-conditional-packages:holder-configuration-g;
                    description "none";
                }
                container holder-current-problems {
                    uses onf-core-model-conditional-packages:holder-current-problems-g;
                    description "none";
                }
                container holder-status {
                    uses onf-core-model-conditional-packages:holder-status-g;
                    description "none";
                }
                description "none";
            }
            grouping holder-capability-g {
                leaf supported-alarms {
                    type string;
                    config false;
                    description "Available alarms to be listed. Names are to be separated by commas.";
                }
                description "none";
            }
            grouping holder-configuration-g {
                list problem-type-severity-list {
                    key 'problem-type-name';
                    uses onf-core-model-conditional-packages:problem-severity-type-g;
                    description "Severity of the problem to be configured.";
                }
                description "none";
            }
            grouping holder-status-g {
                description "none";
            }
            grouping holder-current-problems-g {
                list current-problem-list {
                    key 'sequence-number';
                    config false;
                    uses onf-core-model-conditional-packages:current-problem-type-g;
                    description "none";
                }
                description "none";
            }


}
